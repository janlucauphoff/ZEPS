# ZEPS_Requirements

## #8: Environment (Container)

### #7: C02 Emission (Functional)
The ship shall produce zero emission

### #9: Water Pollution (Functional)
The ship shall recycle sewage to minimize the water pollution to the river

### #10: Fresh Water (Functional)
The ship shall convert water from the river to drinable water using a water purification system together with a tank for one day

## #11: Self sustainable (Container)

### #12: Solar Power (Functional)
The ship shall have solar panels to generate power

### #13: Energy storage (Functional)
The ship shall have an Energy storage for cruises over a maximum of two weeks

## #14: Electrical (Container)

### #15: Electrical Engines (Functional)
The ship shall have electrical engines to enable zero emission propulsion

### #16: Fuel Cells (Functional)
The ship shall have fuel cells with a H2 tank to provide the main electrical energy

### #17: Backup Battery (Functional)
The ship shall have a second electrical storage for peak loads

### #18: Engine Power (Functional)
The electrical engine power shall be similar / slighlty smaller than the power of the installed diesel engines

### #19: Engine duty (Functional)
The ship shall be able to take trips under full engine power up to 10 hours
